-- Foundry Networks Stacking MIB
-- This MIB provides information about stack topology and member status

FOUNDRY-SN-STACKING-MIB DEFINITIONS ::= BEGIN

IMPORTS
    MODULE-IDENTITY, OBJECT-TYPE, Integer32, Unsigned32
        FROM SNMPv2-SMI
    TEXTUAL-CONVENTION, DisplayString
        FROM SNMPv2-TC
    foundrySnStackingMib
        FROM FOUNDRY-SN-ROOT;

foundrySnStackingMib MODULE-IDENTITY
    LAST-UPDATED "202401170000Z"
    ORGANIZATION "Foundry Networks"
    CONTACT-INFO
        "Foundry Networks
         Technical Support"
    DESCRIPTION
        "MIB for Foundry Networks Stacking functionality"
    ::= { foundrySnStacking 1 }

-- Stack Topology Table
snStackTopoTable OBJECT-TYPE
    SYNTAX SEQUENCE OF SnStackTopoEntry
    MAX-ACCESS not-accessible
    STATUS current
    DESCRIPTION
        "A table containing information about stack topology connections"
    ::= { foundrySnStackingMib 1 }

snStackTopoEntry OBJECT-TYPE
    SYNTAX SnStackTopoEntry
    MAX-ACCESS not-accessible
    STATUS current
    DESCRIPTION
        "An entry containing stack topology information"
    INDEX { snStackTopoLocalUnit, snStackTopoLocalPort }
    ::= { snStackTopoTable 1 }

SnStackTopoEntry ::= SEQUENCE {
    snStackTopoLocalUnit      Integer32,
    snStackTopoLocalPort      Integer32,
    snStackTopoRemoteUnit     Integer32,
    snStackTopoRemotePort     Integer32,
    snStackTopoLinkStatus     INTEGER
}

snStackTopoLocalUnit OBJECT-TYPE
    SYNTAX Integer32 (1..8)
    MAX-ACCESS not-accessible
    STATUS current
    DESCRIPTION
        "The local unit number in the stack"
    ::= { snStackTopoEntry 1 }

snStackTopoLocalPort OBJECT-TYPE
    SYNTAX Integer32 (1..4)
    MAX-ACCESS not-accessible
    STATUS current
    DESCRIPTION
        "The local port number used for stacking"
    ::= { snStackTopoEntry 2 }

snStackTopoRemoteUnit OBJECT-TYPE
    SYNTAX Integer32 (1..8)
    MAX-ACCESS read-only
    STATUS current
    DESCRIPTION
        "The remote unit number connected to this port"
    ::= { snStackTopoEntry 3 }

snStackTopoRemotePort OBJECT-TYPE
    SYNTAX Integer32 (1..4)
    MAX-ACCESS read-only
    STATUS current
    DESCRIPTION
        "The remote port number connected to this port"
    ::= { snStackTopoEntry 4 }

snStackTopoLinkStatus OBJECT-TYPE
    SYNTAX INTEGER {
        up(1),
        down(2),
        unknown(3)
    }
    MAX-ACCESS read-only
    STATUS current
    DESCRIPTION
        "The status of the stack link"
    ::= { snStackTopoEntry 5 }

-- Stack Priority Table
snStackPriorityTable OBJECT-TYPE
    SYNTAX SEQUENCE OF SnStackPriorityEntry
    MAX-ACCESS not-accessible
    STATUS current
    DESCRIPTION
        "A table containing stack priority information for each unit"
    ::= { foundrySnStackingMib 2 }

snStackPriorityEntry OBJECT-TYPE
    SYNTAX SnStackPriorityEntry
    MAX-ACCESS not-accessible
    STATUS current
    DESCRIPTION
        "An entry containing stack priority information"
    INDEX { snStackPriorityUnit }
    ::= { snStackPriorityTable 1 }

SnStackPriorityEntry ::= SEQUENCE {
    snStackPriorityUnit       Integer32,
    snStackPriorityValue      Integer32,
    snStackPriorityRole       INTEGER
}

snStackPriorityUnit OBJECT-TYPE
    SYNTAX Integer32 (1..8)
    MAX-ACCESS not-accessible
    STATUS current
    DESCRIPTION
        "The unit number"
    ::= { snStackPriorityEntry 1 }

snStackPriorityValue OBJECT-TYPE
    SYNTAX Integer32 (0..255)
    MAX-ACCESS read-only
    STATUS current
    DESCRIPTION
        "The priority value for this unit (higher value = higher priority)"
    ::= { snStackPriorityEntry 2 }

snStackPriorityRole OBJECT-TYPE
    SYNTAX INTEGER {
        master(1),
        member(2),
        standby(3)
    }
    MAX-ACCESS read-only
    STATUS current
    DESCRIPTION
        "The current role of this unit in the stack"
    ::= { snStackPriorityEntry 3 }

END
